-- - gss.asn1	ASN.1 definition for GSS.
 -- - Copyright (C) 2003  Simon Josefsson
 -- - Copyright (C) 1997  Internet Society (RFC 2078).

 -- - This file is part of GPL GSS-API.

 -- - GPL GSS-API is free software; you can redistribute it and/or modify
 -- - it under the terms of the GNU General Public License as published by
 -- - the Free Software Foundation; either version 2 of the License, or
 -- - (at your option) any later version.

 -- - GPL GSS-API is distributed in the hope that it will be useful,
 -- - but WITHOUT ANY WARRANTY; without even the implied warranty of
 -- - MERCHANTABILITY or FITNESS FOR A PARTICULAR PURPOSE.  See the
 -- - GNU General Public License for more details.

 -- - You should have received a copy of the GNU General Public License
 -- - along with GPL GSS-API; if not, write to the Free Software
 -- - Foundation, Inc., 59 Temple Place, Suite 330, Boston, MA  02111-1307  USA
 
GSS-API {} DEFINITIONS EXPLICIT TAGS ::=

 -- - This is Section 3.1 from RFC 2078, copyright owned by ISOC, with some
 -- - cosmetic changes made to make it parse with the buggy libtasn1 parser,
 -- - plus a few OIDs added for convenience.

BEGIN

MechType ::= OBJECT IDENTIFIER
-- data structure definitions

-- callers must be able to distinguish among
-- InitialContextToken, SubsequentContextToken,
-- PerMsgToken, and SealedMessage data elements
-- based on the usage in which they occur

InitialContextToken ::=
-- option indication (delegation, etc.) indicated within
-- mechanism-specific token
[APPLICATION 0] IMPLICIT SEQUENCE {
        thisMech MechType,
        innerContextToken ANY DEFINED BY thisMech
           -- contents mechanism-specific
           -- ASN.1 structure not required
        }

KerberosV5MechType OBJECT IDENTIFIER ::= {iso(1)
					  member-body(2) 
					  US(840)
					  mit(113554)
					  infosys(1)
					  gssapi(2)
					  krb5(2)}

END
